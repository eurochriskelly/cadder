;; POLYGON((4.892008299999999 52.39873899999998,4.8918657 52.398330999999985,4.893637199999999 52.398323000000005,4.8944244 52.398495,4.8954535 52.39836500000001,4.895572199999999 52.398708,4.8956227 52.39873499999999,4.895753899999999 52.39908199999999,4.8960958 52.399040000000014,4.896385700000001 52.399265000000014,4.8964381 52.39925800000003,4.8968544 52.39930699999999,4.8969569 52.399372,4.8970975999999995 52.39939900000002,4.8976636000000005 52.399799,4.897823299999999 52.399928999999986,4.8969994 52.400318,4.8981271 52.40121500000001,4.8979321 52.401306000000005,4.8968015 52.40041400000001,4.8960061 52.40078399999999,4.8959589 52.40074899999996,4.895830200000001 52.40080600000002,4.8958683 52.400845000000004,4.895348500000001 52.401093,4.8953104 52.401061999999996,4.895026200000001 52.401196,4.8950677 52.40123,4.8949242 52.401295000000005,4.8946018 52.401035000000036,4.8940015 52.39920000000001,4.8921714 52.399208000000016,4.892008299999999 52.39873899999998),(4.894691 52.39936399999999,4.8947139 52.39942899999997,4.8947787 52.399422000000015,4.8948188 52.399508999999995,4.8948002 52.39945599999999,4.8949351 52.399440999999996,4.8949633 52.399490000000014,4.894868399999999 52.399246000000005,4.8948865 52.39929999999998,4.894751500000001 52.399315,4.8947244 52.399265000000014,4.894742 52.39935700000001,4.894691 52.39936399999999),(4.894691 52.39936399999999,4.8947139 52.39942899999997,4.8947787 52.399422000000015,4.8948188 52.399508999999995,4.8948002 52.39945599999999,4.8949351 52.399440999999996,4.8949633 52.399490000000014,4.894868399999999 52.399246000000005,4.8948865 52.39929999999998,4.894751500000001 52.399315,4.8947244 52.399265000000014,4.894742 52.39935700000001,4.894691 52.39936399999999,4.8958502 52.40050099999999),(4.8958688 52.40055100000001,4.895916899999999 52.40054300000003,4.895899799999999 52.40049400000001,4.8958502 52.40050099999999,4.894691 52.39936399999999))


(defun c:dwkt () 

  (defun wkt-to-pointlist (wkt / open close coords pointlist coord pair) 
    ;; Remove "POLYGON((" and "))" from the WKT string
    (setq wkt (substr wkt 10 (- (strlen wkt) 9)))

    ;; Initialize the point list
    (setq pointlist '())

    ;; Find each pair of coordinates
    (while 
      (setq open   (vl-string-search "(" wkt)
            close  (vl-string-search ")" wkt)
            coords (substr wkt (+ open 2) (- close open 1))
            wkt    (substr wkt (+ close 2))
      )
      ;; Process each coordinate pair
      (while (setq comma (vl-string-search "," coords)) 
        (setq pair      (substr coords 1 comma)
              coords    (substr coords (+ comma 2))
              coord     (read (strcat "(" pair ")"))
              pointlist (cons coord pointlist)
        )
      )
    )

    ;; Reverse the point list to maintain the original order
    (reverse pointlist)
  )

  ;; Example usage
  (setq wkt )
  (setq points (wkt-to-pointlist wkt))
  (princ points) ;; Print the points
)


(princ)
